# Requisitos_Güertito

## RC: REQUISITOS CRUZADOS (Container)
Todos los requisitos cruzados con el resto de grupos

### #7: Cerradura (Functional)
En caso de que se detecte por medio de la cerradura que los usuarios están abandonando su casa, recibiremos una señal a nuestro sistema para activar los actuadores en este caso de iluminación exterior del huerto.

### #8: Cocina (Functional)
En el caso de que nuestro sistema determine que los alimentos están listos ya para ser recogidos por el usuario, se le enviará está información al sistema de la cocina para que sean ellos los que lo comuniquen directamente al usuario. En nuestro sistema, este aviso vendrá en forma de notificación a través de nuestra app.

### J*: Puerta para gatos (Functional)
La aplicación de la gatera se conectará por una API a los datos recopilados por el sistema del huerto acerca de la meteorología, y avisará en caso de precipitaciones para poder programar acciones como cerrar la gatera para evitar que el gato salga de la vivienda.

## RF: FUNCIONALES (Container)
Todos los requisitos funcionales

### RFS: Requisitos de sistema (Container)
Todos los requisitos de sistema

#### RFS01: Monitorizar parámetros de cultivo (Functional)
El sistema debe ser capaz de monitorizar los parámetros determinantes en el cultivo de alimentos. Tales parámetros son: temperatura, humedad, viento, calidad del aire, estado de la tierra, estado de la planta, fecha. Estos parámetros serán mostrados al usuario a través de la app y visualizados por el usuario. Este requisito se relaciona con el RNFD02.

#### RFS02S*: Regar huerto (Functional)
El sistema debe ser capaz de regar el huerto a través de los actuadores integrados en él de manera adecuada para la salud de la planta a partir de los parámetros determinantes (temperatura, humedad, viento, calidad del aire, estado de la tierra, estado de la planta, fecha) extraídos de los sensores, la información meteorológica y la propia aplicación. Esta actuación se realizará por el propio usuario y ofrecerá diversas opciones:
• Regar el huerto de manera inmediata: el usuario, activando esta opción, provoca que el huerto comience a regarse de forma inmediata.
• Programar riego del huerto: esta opción permite que se active el riego del huerto de forma remota, mediante la programación de la hora de inicio y la duración del riego.
Cabe destacar que la intensidad de riego del huerto será la misma en ambos casos.

#### RFS03: Acceder a datos meteorológicos (Functional)
El sistema debe ser capaz de acceder a datos meteorológicos fiables y actualizados para la determinación de los valores de los actuadores. Los datos meteorológicos más importantes serán la temperatura, humedad, viento, calidad del aire y pronóstico de lluvia y nieve. El sistema accederá de forma casi inmediata, actualizándose los datos cada media hora. Para ello se necesitará de acceso a internet de forma continua, como es lógico. Este requisito se relaciona con el RFS01.

#### RFS04: Comunicación con otros sistemas (Functional)
El sistema debe ser capaz de enviar comunicarse con otros sistemas inteligentes de la casa, aportando la información relevante (temperatura, humedad, viento, calidad del aire, estado de la tierra, estado de la planta, fecha de recogida del producto) que necesiten en cada caso, pudiéndose añadir nuevos sistemas tras estar en funcionamiento el sistema de “Güertito”. Se relaciona con el requisito RNFD03. Esta comunicación se realizará mediante una conexión WiFi. Además, en la app de nuestro sistema aparecerá una notificación avisándonos de esa conexión con los otros sistemas. En concreto, los sistemas con los que tendrá que conectarse en algún momento son los siguientes:
• Sistema cerradura inteligente.
• Sistema puerta para gatos.
• Sistema cocina inteligente.

#### RFS05: Estimación de recogida de los alimentos (Functional)
El sistema debe ser capaz de estimar una fecha para la recogida de los alimentos sembrados a partir de las estimaciones realizadas en cultivos similares y debe ser facilitada al usuario y estar disponible para otros sistemas que así lo necesiten. Esta estimación, en parte se realiza por la información que aporta la base de datos de cada alimento, si bien es cierto que, durante el proceso de crecimiento, se hará un tratamiento de los datos aportados por sensores de tal forma que esta fecha de recogida se verá afectada por ligeros cambios. Este requisito se relaciona directamente con RFS06.

#### RFS06: Acceso a base de datos de diferentes cultivos (Functional)
El sistema debe tener acceso a una base de datos donde consultar información clave para la siembra, el cuidado y la buena salud del cultivo. En concreto, el sistema deberá ser capaz de recabar:
• Información sobre la temporada clave para la siembra de la planta
• Acciones correctoras para solucionar errores comunes en el cuidado
• Curiosidades específicas de la planta
• Consejos de cuidados para la planta) que usará el sistema para generar y proporcionar información útil al usuario final de la aplicación.
Se relaciona con los requisitos RFS06, RFU01.

### RU: Requisitos de Usuario (Container)
Todos los requisitos de usuario

#### RFU01: Ampliar conocimientos acerca del cuidado de un huerto (Functional)
El sistema debe proporcionar los suficientes datos que ofrezcan al usuario los conocimientos para el cuidado de su huerto. Dichos conocimientos serán: Frecuencia de regado, cantidad de abono, horas de sol, humedad relativa, tiempo de cultivo y datos meteorológicos. Para ello, se nutrirá de una base de datos de cuidado de plantas vía Wi-Fi. Se relaciona con los requisitos RFS06 y RFS05.

#### RFU02*: Ayuda al cuidado de un huerto (Functional)
El usuario debe entender, interpretar y ser capaz de llevar a cabo tareas básicas de mantenimiento de plantas y obtención de los recursos para el cultivo, tales como agua, abono, nutrientes, pesticidas, poda, siembra, recogida del fruto. Para realizar esta ayuda el usuario tendrá a su disposición manuales y documentación a través de la app.

#### RFU03: Sencillez (Functional)
El entorno en disposición del usuario debe ser intuitivo y sencillo. El usuario debe ser capaz de interpretar y ejecutar acciones a través de la aplicación. Entre estas acciones deberá poder añadir/eliminar huertos y plantas, seleccionar todos los parámetros de ajuste nombrados en el requisito RFU08 y navegar por la aplicación, gestionar los datos de perfil de usuario, eliminar su cuenta, actualizar información, obtener ayuda y acceder a las bases de datos. Todo esto viene desglosado en los requisitos RFU04, RFU05, RFU06, RFU07 y RFS01-06. Para todo esto será de vital importancia que el diseño de la interfaz sea lo más cómoda e intuitiva posible.

#### RFU04*: Añadir huerto (Functional)
El usuario debe ser capaz de añadir huertos al sistema. Para ello, como precondición se establece que el usuario esté dado de alta en el sistema, además de haber realizado el log in con anterioridad. Una vez realizada la función, el nuevo huerto aparecerá en la interfaz con el nombre especificado por el usuario, precondición básica para los requisitos RFU05, RFU06 y RFU07.

#### RFU05*: Añadir planta (Functional)
El usuario debe ser capaz de añadir plantas dentro de cada huerto del sistema dentro de la propia aplicación. Las precondiciones necesarias para que esto sea posible serán que el usuario esté dado de alta en el sistema y que haya iniciado sesión además de que exista un huerto creado con anterioridad (RFU04) en el cuál incluir la nueva planta. Este proceso se podrá realizar en múltiples ocasiones y de forma indefinida. Una vez creado el perfil de la nueva planta, se podrán asociar sensores o actuadores a la misma.

#### RFU06*: Eliminar huerto (Functional)
El usuario debe poder eliminar un huerto dentro del sistema. Para ello, previamente debe estar dado de alta en el sistema y haber iniciado sesión. Además, debe existir un huerto creado con anterioridad (RFU04) para ser eliminado. Al eliminar el huerto, se eliminarán de igual forma todas las plantas asociadas al mismo (RFU07).

#### RFU07*: Eliminar planta (Functional)
El usuario debe ser capaz de eliminar plantas dentro de cada huerto del sistema dentro de la propia aplicación. Para ello, el usuario debe estar dado de alta en el sistema y haber iniciado sesión en el mismo. Además, debe existir un huerto asociado al perfil con anterioridad (RFU04) y con plantas añadidas al mismo (RFU05). Esta condición ocurrirá de forma automática en caso de que se cumpla RFU06.

#### RFU08: Control manual de actuadores (Functional)
El usuario dispondrá del control manual de los actuadores en caso de que el sistema autónomo falle o se requiera de una actuación inmediata. Por ello, el usuario deberá disponer de accesibilidad a los actuadores tanto a través de la propia aplicación como de forma física. Este control se deberá producir en caso de que las funciones descritas en el requisito RFS02, de programación del riego y de riego inmediato, fallen. Además, en la aplicación deberá saltar un mensaje de enviar error al soporte técnico.

#### RFU09: Aporte de feedback (Functional)
El usuario debe poder aportar feedback al sistema para actualizar la evolución de las plantas en caso de que esta no coincida con la que el sistema esté evaluando para que el propio sistema proponga nuevas acciones correctoras. Para ello, la aplicación dispondrá de un cuestionario con fitopatologías típicas extraídas de las bases de datos y posibles soluciones a las mismas. Además de este feedback, tanto si se ha descargado la aplicación en el AppStore de Apple o bien a través de Android, se preguntará al usuario la satisfacción con el uso de la aplicación a los pocos días de descargarse.

#### RFU10J**: Identificación única y personal en la aplicación (Functional)
El sistema debe proporcionar un usuario único y personal a cada persona que utilice la aplicación, debiéndose verificar la verdadera identidad de la persona que está usando un determinado usuario. El login en la aplicación se realizará mediante un sistema de verificación en dos pasos, estableciendo una clave única para cada usuario y una verificación vía SMS o correo electrónico. Como precondición se establece que el usuario esté dado de alta en el sistema y haya realizado dicha verificación. Una vez dado de alta se le asignar se podrá asignar un rol al usuario tal y como se indica en el requisito RFU11.

#### RFU11: Nivel de privilegios para cada usuario (Functional)
El sistema debe proporcionar un nivel de privilegios determinado a cada usuario del sistema de manera que no todos tenga en acceso global a todas las acciones o información de cada huerto. Por ejemplo, tal y como se ha descrito en los casos de uso, el usuario externo sólo podrá acceder a las funcionalidades descritas en la figura 2 en la descripción general de los casos de uso. Lo mismo pasa con los otros tipos de usuario. Dentro de cada huerto, deben existir los privilegios de “Administrador”, “Moderador” y “Usuario externo” para cada uno de los usuarios. Este requisito tiene de precondición el requisito RFU10.

## RNF: REQUISITOS NO FUNCIONALES (Container)
Todos lso requisitos no funcionales

### RNFD: Requisitos Desempeño (Container)
Todos los requisitos no funcionales de desempeño

#### RNFD01: Velocidad de actuación de los actuadores (Functional)
Los actuadores deben responder antes de 1 segundo tras mandar una acción de actuación desde la aplicación. Esto ocurrirá cuando el sistema lo considere oportuno debido a condiciones meteorológicas o condiciones específicas de la planta extraídas directamente de las bases de datos. Además, como ya se dijo en el requisito RFS02, también se debe cumplir esa velocidad para cuando el usuario selecciona la opción de regar desde la app. Sin embargo, este tiempo de respuesta de 1 segundo se puede aumentar hasta los 3 segundos cuando la función de regar se produce de forma autónoma, es decir, mediante la programación de un riego.

#### RNFD02: Recogida de información de los sensores (Functional)
Los sensores deberán recoger información en todo momento que sea requerido por el sistema y enviar la información correctamente de vuelta al sistema para que este evalúe la situación. En concreto, los sensores de temperatura y humedad deben enviar información a la placa cada 2 segundos, teniendo la capacidad de transmitir la señal de hasta 20 metros. El sensor de luminosidad, encargado de enviar los datos a los actuadores de luz, suelen tener un tiempo de respuesta de entre 25 y 30 ms. Esta acción será requerida por el sistema al menos una vez cada tres días para evaluar la evolución del huerto, en caso de que el sistema detecte algún problema en la evolución este pedirá información 1 vez al día a lo largo de la semana siguiente a la realización de los cambios efectuados para solventar el problema en el huerto.

#### RNFD03: Comunicación entre partes del sistema (Functional)
Deberá existir una comunicación continua a lo largo del tiempo entre las diferentes partes del sistema. Esto implicará que desde que se implante el huerto y se haya creado en la aplicación se mantendrá la comunicación entre las diferentes partes del sistema hasta el momento en el que el huerto sea eliminado de la aplicación. Se enviará una señal al día de verificación en la comunicación entre sensores y microcontroladores, así como microcontroladores con el sistema en caso de que ese día no fuese necesario la recogida de información dispuesta en RNFD02. Por ejemplo, la comunicación entre el ordenador para el tratamiento de datos y los microcontroladores Arduino se produce a través de un módulo WiFi tal y como se explicó en el apartado Interfaces hardware, y para otras tareas de mantenimiento, reposición, o implementación del software, la comunicación se realizará a través del Puerto Serie. La comunicación entre los sensores y los microcontroladores se realizará mediante el protocolo 1-wire, lo que hace que la integración entre los sensores en el proyecto sea rápida y sencilla.

#### RNFD04Jg*: Conexión con parte meteorológico (Functional)
El sistema deberá comunicarse con el parte meteorológico una vez al día. Esto ocurrirá independientemente de lo que requiera el usuario, el que podrá pedir al sistema que actualice más veces durante el día en caso de que él lo requiera. En cada actualización recogerá la información de los próximos 2 días acerca de humedad, temperatura, precipitaciones, viento y calidad del aire. Además, se debe ir actualizando el parte meteorológico cada media hora, tal y como se ha especificado en el requisito RFS03. Se debe verificar, además, a través de un mensaje mostrado en la app, que el parte se ha actualizado correctamente. En caso de no conectarse al parte meteorológico, se mostrará un aviso de error en la aplicación, para que el usuario compruebe su conexión a internet. En cualquier caso, el sistema deberá dejar al usuario acceder al resto de funcionalidades.

### RNFS: Requisitos Seguridad (Container)
Todos los requisitos no funcionales de seguridad

#### RNFS01: Encriptación de los datos almacenados (Functional)
Los datos almacenados en el sistema, así como toda la información que se vaya creando relacionada con los cultivos, deben estar encriptados en la base de datos para evitar la filtración de la información relativa a los usuarios.

#### RNFS02: Datos almacenados de forma anónima (Functional)
Los datos almacenados deben estar almacenados de forma anónima para la mantener la privacidad de los usuarios. En ningún caso se hará esta información pública.

#### RNFS03: Accesibilidad a la información del huerto (Functional)
Los monitorización y control de los huertos debe ser accesible solo por el dueño del huerto y a los que ha otorgado permisos anteriormente. Al creador del huerto en la aplicación se le otorgarán los permisos de dueño, posteriormente el resto de los usuarios podrán acceder a la información y control del huerto siempre que esté se lo permita especificando los permisos que le quiere ceder. Además, el protocolo de traspaso de permisos del usuario dueño del cultivo al usuario tercero que se encarga de vigilar el huerto cuando el dueño así lo requiera, debe seguir estrictamente los pasos enunciados en el caso de uso Añadir visualización de huerto externo.

#### RNFS04: Encapsulado y aislamiento de conexiones eléctricas en hardware (Functional)
Los diferentes dispositivos hardware del sistema deben encapsularse de tal manera que asegure el aislamiento eléctrico del exterior, evitando posibles problemas de seguridad en la manipulación o mal funcionamiento en las mismas.

#### RNFS05: Encapsulado de los microcontroladores, sensores y actuadores (Functional)
Dado que los microcontroladores, sensores y actuadores van a estar expuestos a la intemperie y a la manipulación, deben de tener un encapsulado que asegure una protección IP65 contra agua y polvo para evitar la rápida degradación de nuestro sistema y posibles problemas de seguridad relacionados con la misma.

### RNFMEJ*: Requisitos de Manejo de Errores (Container)
Todos los requisitos de manejo de errores

#### RNFME01: Fallo en el riego (Functional)
El sistema debe notificar y reportar al usuario en caso de fallo en el riego vía la aplicación para la manipulación manual posterior. En este tipo de fallo se incluyen, el fallo de un actuador, así como los requisitos RNFD01 Y RNFD03. El aviso de fallo se debe dar como máximo en los 5 segundos posteriores al fallo del actuador, para corroborar que no es un cambio de decisión en el usuario.

#### RNFME02: Fallo en microcontroladores (Functional)
El sistema debe notificar y reportar al usuario en caso de fallo en los microcontroladores vía la aplicación para la reparación posterior. Esto se detectará por medio del requisito RNFD03.

#### RNFME03: Fallo en los sensores (Functional)
El sistema debe notificar y reportar al usuario en caso de fallo en los sensores vía la aplicación para la reparación posterior. Esto se detectará por medio del requisito RNFD02. En caso de que se produzca este tipo de error, se permitirá realizar las acciones típicas del sistema al usuario, tales como activar el riego, abonos, luces, humedad, pero dejando bien claro que queda bajo su decisión debido a que los sensores no son capaces de recabar datos correctamente.

#### RNFME04: Fallo en el servidor (Functional)
En caso de fallo en el servidor se les enviará un correo a todos los usuarios perjudicados con el posible tiempo de reparación, así como mantenimientos periódicos que se produzcan en él. Si se produce un fallo en el servidor de que no deja recabar datos de determinadas plantas o abonos, no se permitirá seguir debido a que se ha producido una falta de información.

#### RNFME05: Fallo en la comunicación (Functional)
En caso de fallo en la comunicación entre sistemas se notificará del problema a los usuarios vía aplicación, así como en el caso de reparación. Esto se detectará por medio de los requisitos RNFD02 Y RNFD03.

### RNFU: Requisitos de Usabilidad (Container)
Todos los requisitos no funcionales de usabilidad

#### RNFU01: Capacidad de reinicio (Functional)
Los diferentes elementos que componen el sistema deben disponer de elementos que permitan el apagado, encendido y reset. Esto será necesario en caso de no querer utilizar ciertos dispositivos ya instalados o debido a que sea requerido para solucionar un fallo típico del sistema.

#### RNFU02: Posibilidad de borrado de datos (Functional)
Se debe disponer de una opción de borrado de datos del sistema de los usuarios. En caso de que los usuarios quieran eliminar la aplicación debido a cualquier razón personal al usuario podrá eliminarla y toda la información que esta incluye sobre él.

#### RNFU03: Opción de control manual (Functional)
Se debe poder de controlar manualmente todas aquellas características que sean planificadas para ser ejecutadas de forma automática por el sistema. En caso de que la comunicación entre las diferentes partes del sistema falle, así como nuestro servidor, los usuarios dispondrán del control manual de los dispositivos para que este siga funcionando correctamente hasta que se solucionen los problemas aparecidos.

### RNFD: Requisitos de Disponibilidad (Container)
Todos los Requisitos de Disponibilidad

#### RNFDI01: Estado del servidor (Functional)
El servidor deberá estar siempre disponible y operativo para poder realizar el seguimiento de la información aportada por los microcontroladores. La información aportada por los microcontroladores se puede realizar en cualquier momento del día, así como las comunicaciones entre diferentes sistemas. El único momento en el que no se encontrará disponible será en el reinicio diario a las 3 AM y durante la manipulación y mantenimiento de este.

#### RNFDI02: Estado de los microcontroladores (Functional)
Los microcontroladores deberán estar siempre disponibles y operativos para realizar el seguimiento de la información aportada por los sensores y regulando la actuación de los actuadores. La actuación de los actuadores se pedirá cuando sea necesario, determinado por el sistema, de esta manera los microcontroladores deberán estar disponibles también en todo momento. El único momento en el que no se encontrará disponible será durante la manipulación y mantenimiento de este.

#### RNFDI03: Estado de los sensores (Functional)
Los sensores deberán estar siempre disponibles y operativos para aportar los datos necesarios y requeridos por los microcontroladores. El sistema puede requerir la información deseada en cualquier momento, por ello los sensores deberán estar operativos y disponible en todo momento. El único momento en el que no se encontrará disponible será durante la manipulación y mantenimiento de este.

#### RNFDI04: Estado de los actuadores (Functional)
Los actuadores deberán estar siempre disponibles y operativos para actuar en caso de que se lo solicité alguno de los microcontroladores. Se podrá requerir la actuación por el sistema en cualquier momento, por ello deberán estar activos continuamente. El único momento en el que no se encontrará disponible será durante la manipulación y mantenimiento de este.

### RNFN: Requisitos de Normativa (Container)
Todos los Requisitos de Normativa

#### RNFN01: Normativa de riego (Functional)
Desde el diseño conceptual del sistema, hasta la puesta a punto de este, pasando por la implementación e integración con los sensores, actuadores y computadores, se debe seguir la normativa vigente y aplicable relacionada con los sistemas de riego. En concreto, se debe seguir la siguiente normativa: • UNE 68072:1986, relacionada con el material de riego, aspersores, requisitos generales y métodos de ensayo.
• UNE-EN 12484-4:2003, relacionada con los sistemas de riego automático en espacios verdes, además de la instalación y recepción.

#### RNFN02: Normativa de productos químicos (Functional)
Se debe cumplir la normativa UNE-EN ISO 13693-1:2018, relacionada con la aplicación de productos químicos mediante el riego (fertiirrigación).
